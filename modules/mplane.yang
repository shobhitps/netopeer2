module mplane {

  namespace "urn:mplane";
  prefix e;

  rpc start {
        input {
            leaf name {
                type string;
            }
            leaf arg1 {
                type int64;
            }
        }

        output {
            leaf ret {
                type int64;
            }
        }

  }

  rpc stop {
        input {
            leaf arg {
                type string;
            }
        }

        output {
            leaf ret {
                type int64;
            }
        }

  }

}
