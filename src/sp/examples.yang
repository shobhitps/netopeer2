module examples {
    namespace "urn:examples";
    prefix e;

    container cont {
        leaf l {
            type string;
        }
    }

    container stats {
        config false;
        leaf counter {
            type uint64;
        }

        leaf counter2 {
            type uint64;
        }
    }

    rpc oper {
        input {
            leaf arg {
                type string;
            }
        }

        output {
            leaf ret {
                type int64;
            }
        }
    }

    rpc start {
        input {
            leaf arg {
                type string;
            }
        }

        output {
            leaf ret {
                type int64;
            }
        }
    }

    notification notif {
        leaf val {
            type decimal64 {
                fraction-digits 2;
            }
        }
    }
}
